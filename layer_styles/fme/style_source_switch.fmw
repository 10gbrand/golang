FME workspace style_source_switch.fmw

Parameters:
- DataPathToReplace = "http://localhost:4200/assets/springfield/   # "" DataPathToReplace
- DataPath = "/   # "" DataPath
- VectorTypeToReplace = "type": "geojson"
- VectorType = "type": "vector"
- VectorSufixToReplace = .geojson"
- VectorSufix = .fgb"
- RasterPathToReplace = "tiles": [ "http://localhost:4200/tiles/
- RasterPath = "url": "/
- RasterSufixToReplace = /{z}/{x}/{y}.png"
- RasterSufix = .tif"
- inputDir = \\wsl.localhost\Ubuntu\home\mate01\git\ogcStyleTools\style-src\style\layer_styles\result   # INCLUDE_WEB_BROWSER inputDir
- outputDir = \\wsl.localhost\Ubuntu\home\mate01\git\ogcStyleTools\style-src\style\layer_styles\result\out   # INCLUDE_WEB_BROWSER outputDir

Creator
    GEOMTYPE = Geometry Object
    NUM = 1
    CREATED -> FeatureReader_2 [INITIATOR]
FeatureReader_2
    ATTRIBUTES = PATH,"path_unix,path_windows,path_rootname,path_filename,path_extension,path_directory_unix,path_directory_windows,path_type,fme_geometry{0}"
    ATTR_ACCUM_MODE = Only Use Result
    COMBINE_GEOM = Use Result
    DATASET = $(inputDir)
    FORMAT = PATH
    ORDER_RESULTS = No
    OUTPUT_FEATURES_DISPLAY = Schema and Data Features
    PATH_GLOB_PATTERN = *
    PATH_HIDDEN_FILES = INCLUDE
    PATH_NO_EMPTY_PROPERTIES = YES
    PATH_OFFSET_DATETIME = yes
    PATH_RECURSE_DIRECTORIES = NO
    PATH_RETRIEVE_FILE_PROPERTIES = NO
    PATH_TYPE = ANY
    PATH_USE_NON_STRING_ATTR = yes
    PATH -> Tester
Tester
    BOOL_OP = OR
    TEST_CLAUSE = TEST @Value(path_type) = file
    TEST_MODE = TEST
    PASSED -> FeatureReader [INITIATOR]
FeatureReader
    ATTRS_TO_EXPOSE = text_line_data fme_feature_type
    ATTR_ACCUM_MODE = Merge Initiator and Result
    ATTR_CONFLICT_RES = Use Result
    ATTR_IGNORE_NULLS = No
    COMBINE_GEOM = Use Result
    DATASET = @Value(path_windows)
    FORMAT = TEXTLINE
    ORDER_RESULTS = No
    OUTPUT_FEATURES_DISPLAY = Schema and Data Features
    TEXTLINE_CREATE_FEATURE_TABLES_FROM_DATA = Yes
    TEXTLINE_ENCODING = windows-1252
    TEXTLINE_READ_WHOLE_FILE_AT_ONCE = YES
    <OTHER> -> DataPath
FeatureWriter
    DATASET = $(outputDir)\@Value(path_filename)
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written

Bookmark: StringReplacer
DataPath: StringReplacer
    CASE = NO
    FIND_TEXT = $(DataPathToReplace)
    NO_MATCH = _FME_NO_OP_
    REGEXP = NO
    REPLACE_TEXT = $(DataPath)
    SRC_ATTRS = text_line_data
    -> VectorType
VectorType: StringReplacer
    CASE = NO
    FIND_TEXT = $(VectorTypeToReplace)
    NO_MATCH = _FME_NO_OP_
    REGEXP = NO
    REPLACE_TEXT = $(VectorType)
    SRC_ATTRS = text_line_data
    -> VectorSufix
VectorSufix: StringReplacer
    CASE = NO
    FIND_TEXT = $(VectorSufixToReplace)
    NO_MATCH = _FME_NO_OP_
    REGEXP = NO
    REPLACE_TEXT = $(VectorSufix)
    SRC_ATTRS = text_line_data
    -> RasterPath
RasterPath: StringReplacer
    CASE = NO
    FIND_TEXT = $(RasterPathToReplace)
    NO_MATCH = _FME_NO_OP_
    REGEXP = NO
    REPLACE_TEXT = $(RasterPath)
    SRC_ATTRS = text_line_data
    -> RasterSufix
RasterSufix: StringReplacer
    CASE = NO
    FIND_TEXT = $(RasterSufixToReplace)
    NO_MATCH = _FME_NO_OP_
    REGEXP = NO
    REPLACE_TEXT = $(RasterSufix)
    SRC_ATTRS = text_line_data
    -> FeatureWriter [text_line]
